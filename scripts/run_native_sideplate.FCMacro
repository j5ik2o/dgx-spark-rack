"""FreeCAD GUIで左側板の作成と評価を実行する。既存出力は上書きしない。"""
from pathlib import Path
import sys

sys.path.insert(0, str(Path(__file__).resolve().parent))
from freecad_sideplate import create
from check_freecad_sideplate import OUT, main

if (OUT / "side-L-native.FCStd").exists():
    raise FileExistsError("新規評価用の出力先を指定してください")
create()
main()
