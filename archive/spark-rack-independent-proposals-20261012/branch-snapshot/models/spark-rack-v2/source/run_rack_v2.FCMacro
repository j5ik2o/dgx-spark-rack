# FreeCADから案Aを生成する実行入口。形状定義は rack_v2_layout.py / rack_v2_parameters.py。
import os
src = os.path.dirname(os.path.abspath(__file__))
os.environ['RACK_V2_SRC'] = src
exec(open(os.path.join(src, 'build_rack_v2.py'), encoding='utf-8').read(), {'__file__': os.path.join(src, 'build_rack_v2.py'), '__name__': '__main__'})
