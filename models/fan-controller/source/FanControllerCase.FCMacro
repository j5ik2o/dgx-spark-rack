"""ファンコンケースをPythonの正本から生成する入口。"""
from pathlib import Path
import runpy
import sys
import importlib

for name in ('edge_finishing','controller_mount'):
    if name in sys.modules:
        importlib.reload(sys.modules[name])

runpy.run_path(str(Path(__file__).resolve().with_name("build_fan_controller.py")), run_name="__main__")
